module svi {

    namespace "https://www.ctin.vn/modules/svi";
    prefix svi;
    yang-version 1.1;

    import ietf-inet-types {
        prefix inet;
    }
    import tailf-common {
        prefix tailf;
    }
    import tailf-ncs {
        prefix ncs;
    }

    description
      "This is SVI Python service package.";

    revision 2023-09-18 {
        description
          "Initial revision.";
    }

    augment /ncs:services {
        list svi {
            description
              "SVI Python Service";

            key name;
            leaf name {
                tailf:info "Unique service id";
                tailf:cli-allow-range;
                type string;
            }

            uses ncs:service-data;
            ncs:servicepoint svi-servicepoint;

            leaf vlan-id {
                tailf:info "Unique VLAN ID";
                mandatory true;
                type uint32 {
                    range "1..4096";
                }
            }

            // may replace this with other ways of refering to the devices.
            list device {
                tailf:info "L3 Switch";
                key name;

                leaf name {
                    tailf:info "Device name";
                    type leafref {
                        path "/ncs:devices/ncs:device/ncs:name";
                    }
                    must "starts-with(current(), 'SW')" {
                        error-message
                          "Only SW devices can be selected.";
                    }
                }

                leaf ip-prefix {
                    when "count(../../device[name != current()/../name]/ip-prefix) = 0";
                    tailf:info "Unique IPv4 prefix for L3 VLAN interface";
                    type inet:ipv4-prefix;
                }

                list interface {
                    tailf:info "Ethernet interface";
                    key "intf-type intf-id";

                    leaf intf-type {
                        tailf:info "Ethernet Interface Type";
                        type enumeration {
                            enum Ethernet;
                            enum FastEthernet;
                            enum GigabitEthernet;
                        }
                    }

                    leaf intf-id {
                        tailf:info "Ethernet Interface ID";
                        type string;
                    }
                }
            }

            tailf:action self-test {
                tailf:info "Perform self-test of the service";
                tailf:actionpoint svi-self-test;
                output {
                    leaf success {
                        type boolean;
                    }
                    leaf message {
                        type string;
                        description
                          "Free format message.";
                    }
                }
            }
        }
    }
}
